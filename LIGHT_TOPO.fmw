FME workspace LIGHT_TOPO.fmw

Parameters:
- DestDataset_GEODATABASE_FILE =
- FEATURE_TYPES_2 =
- SourceDataset_GEODATABASE_FILE_3 =

Readers:
- GEODATABASE_FILE_1: GEODATABASE_FILE from $(SourceDataset_GEODATABASE_FILE_3)

Writers:
- GEODATABASE_FILE_2: GEODATABASE_FILE to $(DestDataset_GEODATABASE_FILE)

Bookmark: 1: Reading & Filtering
Imavers (reader GEODATABASE_FILE_1)
    attributes: Objectid integer, Schemaname char(24), Version char(6), Notes char(80), ARM_IDENT char(3), Achemine char(50), Adate date, Adresse char(50), Agent char(50), Altitude double, Amperage integer, Angle double, AnnotationClassID integer, Aout integer, Avril integer, Axesensibl char(3), Bold smallint, CODE_A char(7), CODE_ANT char(20), CODE_S char(7), COD_ARMOIR char(13), CONTI_TERR char(3), Cavance double, Cclasse char(50), Cetat char(50), CharacterSpacing double, CharacterWidth double, Civilite char(25), Classe char(50), Cle char(50),
      Cmarque char(50), Cmodele char(50), Codcomm char(6), Code_voie char(4), Codepost char(5), Coment char(50), Commune char(32), Compos char(50), Couleur char(50), Couleurp char(50), Cout_eff double, Cout_prev double, Cout_unit double, Ctype char(50), Culot char(50), DISTR_CABL char(11), DOM char(12), Date_deb date, Date_dem date, Date_entr date, Date_env date, Date_fin date, Date_int date, Date_prev date, Date_rea date, Datedv date, Datefv date, Dateinst date, Decembre integer, Desc_int char(128),
      Desc_pan char(128), Desc_real char(128), Descript char(32), Diametre char(50), Dimensions char(50), Doc blob, Dom char(50), Dt_classe char(3), Dt_source char(255), Echelle integer, Edfcomp char(20), Edfnum char(20), Email char(50), Etat char(50), F_id_node integer, FeatureID integer, Fevrier integer, Fixation char(50), FlipAngle double, Fonction char(50), FontLeading double, FontName char(255), FontSize double, Forme char(50), Fourreau char(50), Hauteur double, HorizontalAlignment smallint, ID_A char(13), ID_T char(13), ID_TERRAIN char(50),
      INSEE char(5), Id_agent integer, Id_arc integer, Id_cof integer, Id_dem integer, Id_detail integer, Id_detobj integer, Id_fou integer, Id_itv integer, Id_lam integer, Id_lat integer, Id_mat integer, Id_node integer, Id_obj char(16), Id_rsys integer, Id_site integer, Id_sope integer, Id_ssys integer, Imarole char(254), Implant char(50), Imputation char(50), Isole integer, Italic smallint, Janvier integer, Juillet integer, Juin integer, Label char(50), Layer char(32), Letat char(50), Lmarque char(50),
      Lmodele char(50), Longueur double, Ltype char(50), Ltypea char(50), Lvariateur char(50), Mai integer, Marque char(50), Mars integer, Materiau char(50), Matricule char(50), Metier char(50), Modele char(50), NAT_CONDUC char(10), NB_PTLUM smallint, NEUTRE_COM char(3), NUM_DEPA char(3), Natcourant char(50), Nature char(50), Nbbornes integer, Nom char(32), Nom_voie char(50), Nombre integer, Novembre integer, Num_voie char(8), Numero char(20), Obj char(16), Octobre integer, Organecom char(50), Override integer, PDL_ERDF char(20),
      PUI_SOUS char(4), Path char(128), Pathdoc char(128), Prenom char(50), Profondeur double, Puissance double, Puissancec integer, Puissancei double, Puissances double, Quantite double, Rivoli char(4), SOURCE char(50), Sect_cable char(50), Secteur char(20), Septembre integer, Sequence char(32), Sforme char(50), Shape_Area double, Shape_Length double, Shauteur double, Smateriau char(50), Status smallint, Statut char(25), Stype char(50), Surface double, Symbol integer, SymbolID integer, TRAPPE char(3), TYPE_CROSS char(20), T_id_node integer,
      Tel char(12), Tempcoul integer, Tension double, Tensionf double, Tensiont double, Terrem char(50), Terrev integer, TextString char(255), Tmplname char(32), Tourpro char(50), Type char(50), Type_voie char(16), Underline smallint, Utilisatio char(50), Valcur integer, Valmax integer, Valmin integer, Variateur integer, VerticalAlignment smallint, Vie integer, Viee integer, Winident char(50), WordSpacing double, XOffset double, YOffset double, ZOrder integer
    -> AttributeFilter
AttributeFilter
    ATTR_NAME = fme_feature_type
    ATTR_VALUES = <Empty>,<Missing>,<Null>,<Unfiltered>,Imarole,Imavers,lum_arc,lum_cof,lum_lat,lum_lut,lum_noeu,lum_nome,lum_sup,sequence
    lum_arc -> Junction_4
    lum_lat -> Junction_5
    lum_noeu -> Junction
Junction_4
    -> CoordinateExtractor_2
    -> FeatureMerger [REQUESTOR]
    -> CoordinateExtractor_5
    -> TopologyBuilder
    -> PointOnLineOverlayer [LINE]
Junction_5
    -> PointOnLineOverlayer [POINT]

Bookmark: 2: Check for Missing Node & Add new Ones & Nodes Traitements
Junction
    -> Junction_6
    -> SpatialRelator [Supplier]
TopologyBuilder
    ALLOW_CYCLES = No
    BOUNDING_EDGES = All
    CLEANING_TOLERANCE = 0
    DEAGGREGATE_INPUT = Yes
    GENERATION_MODE = INTERSECT
    MAX = 0
    OVERLAPPING_MODE = No
    NODE -> SpatialRelator_2 [Requestor]
SpatialRelator_2
    AGGREGATE_HANDLING = Yes
    CALC_CARD = No
    CURVE_BOUNDARY_RULE_PARAM = Default Rule
    LIST_ATTRS_TO_INCLUDE = Id_arc Sense
    LIST_NAME = _related_suppliers1
    PREDICATES = INTERSECTS
    SUCCESS_ATTR = _related_suppliers1
    -> TestFilter_2
TestFilter_2
    DEFAULT_VALUE = <UNFILTERED>
    TEST_LIST = "BOOL_OP,OR,COMPOSITE_TEST,""""""1"""""",TEST_CLAUSE,TEST @Value(_related_suppliers1) >= 1",>=1
    >=1 -> SpatialRelator [Requestor]
SpatialRelator
    AGGREGATE_HANDLING = Yes
    ATTR_ACCUM_MODE = Prefix Supplier
    ATTR_PREFIX = _____
    CALC_CARD = No
    CURVE_BOUNDARY_RULE_PARAM = Default Rule
    IGNORE_NULLS = Yes
    LIST_NAME = _relationships
    PREDICATES = INTERSECTS
    SUCCESS_ATTR = _related_suppliers
    -> StatisticsCalculator
StatisticsCalculator
    CALCULATION_MODE = NUMERIC
    FEAT_STATS = _____Id_node,NUMERIC_MODE,,MAX,,,,,,,,,,
    COMPLETE -> TestFilter
TestFilter
    DEFAULT_VALUE = Missing Node
    TEST_LIST = "BOOL_OP,OR,COMPOSITE_TEST,""""""1"""""",TEST_CLAUSE,TEST @Value(_related_suppliers) >= 1",1
    Missing Node -> AttributeKeeper
AttributeKeeper
    CREATE_BULK_MODE_FEATURES = NO
    KEEP_ATTRS = fme_feature_type,_____Id_node.max
    -> AttributeManager
AttributeManager
    ATTR_TABLE:
      SET_TO fme_feature_type = lum_noeu
      SET_TO Angle = FME_NULL_VALUE
      SET_TO Id_node = @Count(@Value(_____Id_node.max)[,@Evaluate(@int(@Value(_____Id_node.max))+1)])
      SET_TO Type = NTY
      REMOVE _____Id_node.max
    -> Junction_6
Junction_6
    -> TestFilter_5
    -> FeatureClass100 (writer GEODATABASE_FILE_2)
    -> SpatialRelator_3 [Supplier]

Bookmark: 3.1: Extracter les point de Start/End des tronçons
CoordinateExtractor_2
    IND = 0
    MODE = Specify Coordinate
    X_ATTR = X0
    Y_ATTR = Y0
    Z_ATTR = Z0
    -> AttributeCreator_11
AttributeCreator_11
    ATTR_TABLE = SET_TO Sense = From
    -> START_PT_3
START_PT_3: VertexCreator
    MEASURE_TYPE = Continuous
    MODE_NAME = Replace with Point
    XVAL = @Value(X0)
    YVAL = @Value(Y0)
    -> Junction_10
Junction_10
    -> SpatialRelator_3 [Requestor]
    -> SpatialRelator_2 [Supplier]
CoordinateExtractor_5
    IND = -1
    MODE = Specify Coordinate
    X_ATTR = X1
    Y_ATTR = Y1
    Z_ATTR = Z1
    -> AttributeCreator_13
AttributeCreator_13
    ATTR_TABLE = SET_TO Sense = To
    -> END_PT_3
END_PT_3: VertexCreator
    MEASURE_TYPE = Continuous
    MODE_NAME = Replace with Point
    XVAL = @Value(X1)
    YVAL = @Value(Y1)
    -> Junction_9
Junction_9
    -> SpatialRelator_3 [Requestor]
    -> SpatialRelator_2 [Supplier]

Bookmark: 5: Filter Nodes Type
TestFilter_5
    DEFAULT_VALUE = <UNFILTERED>
    TEST_LIST = "BOOL_OP,OR,COMPOSITE_TEST,""""""1"""""",TEST_CLAUSE,TEST @Value(Type) = COF",COF,"BOOL_OP,OR,COMPOSITE_TEST,""""""1"""""",TEST_CLAUSE,TEST @Value(Type) = SUP",SUP
    COF -> SpatialRelator_5 [Supplier]
    COF -> SpatialRelator_7 [Supplier]
    SUP -> SpatialRelator_4 [Supplier]

Bookmark: 3: From/To Nodes & Arcs Traitements
SpatialRelator_3
    AGGREGATE_HANDLING = Yes
    CALC_CARD = No
    CURVE_BOUNDARY_RULE_PARAM = Default Rule
    LIST_ATTRS_TO_INCLUDE = Id_node
    LIST_NAME = _relationships
    PREDICATES = INTERSECTS
    SUCCESS_ATTR = _related_suppliers
    -> Aggregator
Aggregator
    ACCUM_ATTRS_NAME = Use Attributes From One Feature
    AGGREGATE_TYPE = Homogeneous Collection (If Possible)
    GROUP_BY = Id_arc
    LIST_ATTRS_TO_INCLUDE = Sense Id_arc _relationships{}.Id_node
    LIST_NAME = test
    MODE = Geometry - Assemble One Level
    SEP = ,
    AGGREGATE -> FeatureMerger [SUPPLIER]
FeatureMerger
    ATTR_ACCUM_MODE = Merge Supplier
    ATTR_CONFLICT_RES = Use Supplier
    GEOM_TYPE = Build Lines From Points
    IGNORE_NULLS = No
    JOIN_KEYS = @Value(Id_arc) @Value(Id_arc) AUTO
    MERGE_TYPE = Attributes Only
    PROCESS_DUPS = YES
    REJECT_NULL_MISSING_KEYS = No
    SUPPLIERS_FIRST = No
    MERGED -> AttributeCreator
AttributeCreator
    ATTR_TABLE:
      SET_TO F_id_node = FME_CONDITIONAL:DEFAULT_VALUE'_FME_NO_OP_'BOOL_OP;AND;COMPOSITE_TEST;1 AND 2;TEST @Value(test{0}.Sense) = From;TEST @Value(test{1}.Sense) = To'@Value(test{0}._relationships{0}.Id_node)'BOOL_OP;AND;COMPOSITE_TEST;1 AND 2;TEST @Value(test{0}.Sense) = To;TEST @Value(test{1}.Sense) = From'@Value(test{1}._relationships{0}.Id_node)'FME_NUM_CONDITIONS3___
      SET_TO T_id_node = FME_CONDITIONAL:DEFAULT_VALUE'_FME_NO_OP_'BOOL_OP;AND;COMPOSITE_TEST;1 AND 2;TEST @Value(test{0}.Sense) = From;TEST @Value(test{1}.Sense) = To'@Value(test{1}._relationships{0}.Id_node)'BOOL_OP;AND;COMPOSITE_TEST;1 AND 2;TEST @Value(test{0}.Sense) = To;TEST @Value(test{1}.Sense) = From'@Value(test{0}._relationships{0}.Id_node)'FME_NUM_CONDITIONS3___
    -> AttributeKeeper_2
Note: ARC
AttributeKeeper_2
    CREATE_BULK_MODE_FEATURES = NO
    KEEP_ATTRS = fme_feature_type,Altitude,Codepost,Commune,Compos,Diametre,Dt_classe,Dt_source,Etat,Fonction,Fourreau,ID_T,Id_arc,Implant,Isole,Longueur,Modele,Natcourant,Nom_voie,Profondeur,Sect_cable,Secteur,Symbol,T_id_node,Terrem,Terrev,Type,Type_voie,Utilisatio,F_id_node,CODE_A,NUM_DEPA,Id_detobj,Id_obj,Obj,Objectid
    -> Aggregator_2
    -> FeatureClass1 (writer GEODATABASE_FILE_2)
    -> Junction_3
FeatureClass1 (writer GEODATABASE_FILE_2)
    attributes: F_id_node integer, T_id_node integer, Objectid integer, Altitude double, CODE_A char(7), Codepost char(5), Commune char(32), Compos char(50), Diametre char(50), Dt_classe char(3), Dt_source char(255), Etat char(50), Fonction char(50), Fourreau char(50), ID_T char(13), Id_arc integer, Id_detobj integer, Id_obj char(16), Implant char(50), Isole integer, Longueur double, Modele char(50), NUM_DEPA char(3), Natcourant char(50), Nom_voie char(50), Obj char(16), Profondeur double, Sect_cable char(50), Secteur char(20), Symbol integer,
      Terrem char(50), Terrev integer, Type char(50), Type_voie char(16), Utilisatio char(50)

Bookmark: 6.3: Id_arc For LAT
Junction_3
    -> SpatialRelator_7 [Requestor]
    -> FeatureJoiner [LEFT]
SpatialRelator_7
    AGGREGATE_HANDLING = Yes
    ATTR_ACCUM_MODE = Prefix Supplier
    ATTR_PREFIX = _1__
    CALC_CARD = No
    CURVE_BOUNDARY_RULE_PARAM = Default Rule
    IGNORE_NULLS = Yes
    PREDICATES = INTERSECTS
    SUCCESS_ATTR = _related_suppliers
    -> TestFilter_3
TestFilter_3
    DEFAULT_VALUE = <UNFILTERED>
    TEST_LIST = "BOOL_OP,OR,COMPOSITE_TEST,""""""1"""""",TEST_CLAUSE,TEST _1__Id_node ATTRIBUTE_HAS_A_VALUE """,___Id_node ATTRIBUTE_HAS_A_VALUE
    ___Id_node ATTRIBUTE_HAS_A_VALUE -> FeatureJoiner [RIGHT]
FeatureJoiner
    ATTR_CONFLICT_RES = Use Left
    GEOMETRY_HANDLING = Use Left
    JOIN_KEYS = Id_arc Id_arc AUTO
    JOIN_MODE = Inner
    JOINED -> Aggregator_3
    UNJOINED_LEFT -> Aggregator_3
Note: Use Num_DEP é CODE_A to Agregate Arcs
Aggregator_3
    ACCUM_ATTRS_NAME = Use Attributes From One Feature
    AGGREGATE_TYPE = Heterogeneous Collection
    GROUP_BY = CODE_A NUM_DEPA Codepost
    MODE = Geometry - Assemble One Level
    SEP = ,
    AGGREGATE -> AttributeKeeper_4
AttributeKeeper_4
    CREATE_BULK_MODE_FEATURES = NO
    KEEP_ATTRS = _1__Id_node,Id_arc
    -> AttributeRenamer
AttributeRenamer
    ATTR_TABLE = RENAME_SET_DEFAULT Id_arc > _Id_arc
    MISSING_INPUT_ATTRS = REMOVE
    -> SpatialRelator_8 [Supplier]
SpatialRelator_8
    AGGREGATE_HANDLING = Yes
    ATTR_ACCUM_MODE = Merge Supplier
    ATTR_CONFLICT_RES = Use Requestor
    CALC_CARD = No
    CURVE_BOUNDARY_RULE_PARAM = Default Rule
    IGNORE_NULLS = Yes
    PREDICATES = INTERSECTS
    SUCCESS_ATTR = _related_suppliers
    -> AttributeCreator_4
AttributeCreator_4
    ATTR_TABLE = SET_TO Id_arc = @Value(_Id_arc)
    -> CenterPointReplacer
CenterPointReplacer
    POINTTYPE = CENTER
    POINT -> AttributeKeeper_7
AttributeKeeper_7
    CREATE_BULK_MODE_FEATURES = NO
    KEEP_ATTRS = Angle,Cavance,Cetat,Cmarque,Cmodele,CODE_A,CODE_S,Codepost,Commune,Ctype,Date_entr,Hauteur,Id_arc,Id_cof,Id_lat,Id_node,INSEE,Letat,Lmarque,Lmodele,Ltype,Ltypea,Lvariateur,Nom_voie,Notes,NUM_DEPA,Num_voie,Numero,Symbol,Type_voie
    -> FeatureClass100 (writer GEODATABASE_FILE_2)

Bookmark: 6.2: Id_Cof for LAT
Note: Use CODE_A To Aggregate Arcs
Aggregator_2
    ACCUM_ATTRS_NAME = Use Attributes From One Feature
    AGGREGATE_TYPE = Homogeneous Collection (If Possible)
    GROUP_BY = CODE_A Codepost
    MODE = Geometry - Assemble One Level
    SEP = ,
    AGGREGATE -> SpatialRelator_5 [Requestor]
SpatialRelator_5
    AGGREGATE_HANDLING = Yes
    ATTR_ACCUM_MODE = Prefix Supplier
    ATTR_PREFIX = _
    CALC_CARD = No
    CURVE_BOUNDARY_RULE_PARAM = Default Rule
    IGNORE_NULLS = Yes
    PREDICATES = INTERSECTS
    SUCCESS_ATTR = _related_suppliers
    -> AttributeKeeper_3
AttributeKeeper_3
    CREATE_BULK_MODE_FEATURES = NO
    KEEP_ATTRS = _Id_node
    -> SpatialRelator_6 [Supplier]
SpatialRelator_6
    AGGREGATE_HANDLING = Yes
    ATTR_ACCUM_MODE = Prefix Supplier
    ATTR_PREFIX = __
    CALC_CARD = No
    CURVE_BOUNDARY_RULE_PARAM = Default Rule
    IGNORE_NULLS = Yes
    PREDICATES = INTERSECTS
    SUCCESS_ATTR = _related_suppliers
    -> AttributeCreator_3
AttributeCreator_3
    ATTR_TABLE = SET_TO Id_cof = @Value(___Id_node)
    -> AttributeKeeper_6
AttributeKeeper_6
    CREATE_BULK_MODE_FEATURES = NO
    KEEP_ATTRS = Angle,Cavance,Cetat,Cmarque,Cmodele,CODE_A,CODE_S,Codepost,Commune,Ctype,Date_entr,Hauteur,Id_arc,Id_cof,Id_lat,Id_node,INSEE,Letat,Lmarque,Lmodele,Ltype,Ltypea,Lvariateur,Nom_voie,Notes,NUM_DEPA,Num_voie,Numero,Symbol,Type_voie
    -> SpatialRelator_8 [Requestor]

Bookmark: 4: Convert to Buffred Area if LAT not On Line
PointOnLineOverlayer
    DEAGGREGATE_INPUT = Yes
    MEASURE_TYPE = Continuous
    MERGE_MEASURES = Yes
    OV_ATTR = _overlaps
    TOLERANCE = 0
    POINT -> TestFilter_4
TestFilter_4
    DEFAULT_VALUE = <UNFILTERED>
    TEST_LIST = "BOOL_OP,OR,COMPOSITE_TEST,""""""1"""""",TEST_CLAUSE,TEST @Value(_overlaps) = 0",@Value(_overlaps) = 0
    <UNFILTERED> -> Junction_2
    @Value(_overlaps) = 0 -> Bufferer
Bufferer
    ANGLE = 22.5
    CAP_STYLE = Arc
    CORNER_STYLE = Arc
    MODE = AREA
    OFFSET = 2
    OFFSET_UNITS = NONE
    PRECISION = APPROX
    BUFFERED -> Junction_2
Note: LUM_LAT
Junction_2
    -> SpatialRelator_4 [Requestor]

Bookmark: 6.1: ID_NODE for LAT
SpatialRelator_4
    AGGREGATE_HANDLING = Yes
    ATTR_ACCUM_MODE = Prefix Supplier
    ATTR_PREFIX = _
    CALC_CARD = No
    CURVE_BOUNDARY_RULE_PARAM = Default Rule
    IGNORE_NULLS = Yes
    PREDICATES = EQUALS INTERSECTS
    SUCCESS_ATTR = _related_suppliers
    -> AttributeCreator_2
AttributeCreator_2
    ATTR_TABLE = SET_TO Id_node = @Value(_Id_node)
    -> AttributeKeeper_5
AttributeKeeper_5
    CREATE_BULK_MODE_FEATURES = NO
    KEEP_ATTRS = Angle,Cavance,Cetat,Cmarque,Cmodele,CODE_A,CODE_S,Codepost,Commune,Ctype,Date_entr,Hauteur,Id_arc,Id_cof,Id_lat,Id_node,INSEE,Letat,Lmarque,Lmodele,Ltype,Ltypea,Lvariateur,Nom_voie,Notes,NUM_DEPA,Num_voie,Numero,Symbol,Type_voie
    -> SpatialRelator_6 [Requestor]

Bookmark: 7: Output Nods
FeatureClass100 (writer GEODATABASE_FILE_2)
    attributes: Objectid integer, Schemaname char(24), Version char(6), Notes char(80), ARM_IDENT char(3), Achemine char(50), Adate date, Adresse char(50), Agent char(50), Altitude double, Amperage integer, Angle double, AnnotationClassID integer, Aout integer, Avril integer, Axesensibl char(3), Bold smallint, CODE_A char(7), CODE_ANT char(20), CODE_S char(7), COD_ARMOIR char(13), CONTI_TERR char(3), Cavance double, Cclasse char(50), Cetat char(50), CharacterSpacing double, CharacterWidth double, Civilite char(25), Classe char(50), Cle char(50),
      Cmarque char(50), Cmodele char(50), Codcomm char(6), Code_voie char(4), Codepost char(5), Coment char(50), Commune char(32), Compos char(50), Couleur char(50), Couleurp char(50), Cout_eff double, Cout_prev double, Cout_unit double, Ctype char(50), Culot char(50), DISTR_CABL char(11), DOM char(12), Date_deb date, Date_dem date, Date_entr date, Date_env date, Date_fin date, Date_int date, Date_prev date, Date_rea date, Datedv date, Datefv date, Dateinst date, Decembre integer, Desc_int char(128),
      Desc_pan char(128), Desc_real char(128), Descript char(32), Diametre char(50), Dimensions char(50), Doc blob, Dom char(50), Dt_classe char(3), Dt_source char(255), Echelle integer, Edfcomp char(20), Edfnum char(20), Email char(50), Etat char(50), F_id_node integer, FeatureID integer, Fevrier integer, Fixation char(50), FlipAngle double, Fonction char(50), FontLeading double, FontName char(255), FontSize double, Forme char(50), Fourreau char(50), Hauteur double, HorizontalAlignment smallint, ID_A char(13), ID_T char(13), ID_TERRAIN char(50),
      INSEE char(5), Id_agent integer, Id_arc integer, Id_cof integer, Id_dem integer, Id_detail integer, Id_detobj integer, Id_fou integer, Id_itv integer, Id_lam integer, Id_lat integer, Id_mat integer, Id_node integer, Id_obj char(16), Id_rsys integer, Id_site integer, Id_sope integer, Id_ssys integer, Imarole char(254), Implant char(50), Imputation char(50), Isole integer, Italic smallint, Janvier integer, Juillet integer, Juin integer, Label char(50), Layer char(32), Letat char(50), Lmarque char(50),
      Lmodele char(50), Longueur double, Ltype char(50), Ltypea char(50), Lvariateur char(50), Mai integer, Marque char(50), Mars integer, Materiau char(50), Matricule char(50), Metier char(50), Modele char(50), NAT_CONDUC char(10), NB_PTLUM smallint, NEUTRE_COM char(3), NUM_DEPA char(3), Natcourant char(50), Nature char(50), Nbbornes integer, Nom char(32), Nom_voie char(50), Nombre integer, Novembre integer, Num_voie char(8), Numero char(20), Obj char(16), Octobre integer, Organecom char(50), Override integer, PDL_ERDF char(20),
      PUI_SOUS char(4), Path char(128), Pathdoc char(128), Prenom char(50), Profondeur double, Puissance double, Puissancec integer, Puissancei double, Puissances double, Quantite double, Rivoli char(4), SOURCE char(50), Sect_cable char(50), Secteur char(20), Septembre integer, Sequence char(32), Sforme char(50), Shape_Area double, Shape_Length double, Shauteur double, Smateriau char(50), Status smallint, Statut char(25), Stype char(50), Surface double, Symbol integer, SymbolID integer, TRAPPE char(3), TYPE_CROSS char(20), T_id_node integer,
      Tel char(12), Tempcoul integer, Tension double, Tensionf double, Tensiont double, Terrem char(50), Terrev integer, TextString char(255), Tmplname char(32), Tourpro char(50), Type char(50), Type_voie char(16), Underline smallint, Utilisatio char(50), Valcur integer, Valmax integer, Valmin integer, Variateur integer, VerticalAlignment smallint, Vie integer, Viee integer, Winident char(50), WordSpacing double, XOffset double, YOffset double, ZOrder integer
